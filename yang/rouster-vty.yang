// rouster-vty — the vtyd session surface + the configd envelope
// (S11-a M3/M5): exactly what crates/vty/src/config.rs models and
// what the canonical file's top level accepts
// (docs/protocols/config.md §1). The vtysh-compatible grammar is
// the EDGE; this model is what config-mode edits address (the
// translator seam — invariant 5).
module rouster-vty {
  yang-version 1.1;
  namespace "urn:rouster:vty";
  prefix vty;

  import rouster-common {
    prefix rc;
  }

  revision 2026-10-16;

  // ---- display-only frr compatibility lines (B7's observed set) ----

  container frr {
    leaf version {
      type string;
    }
    leaf defaults {
      type string;
    }
  }

  leaf hostname {
    type string;
  }

  container line {
    container vty {
      description "`line vty` — display-only today.";
    }
  }

  // ---- the RESTCONF northbound edge (S12-a M4) ----

  container restconf {
    description
      "restconfd's plane: the canonical file's top-level `restconf { … }`
       stanza, bound here by prepending the stanza's opener to its
       body lines (the linebind's container-walk rule 3). Startup-only
       knobs for restconfd itself — the vtyd bind discipline; the
       security posture (S13-c: the local unix socket is the DEFAULT
       listener, filesystem permissions are the access control, the
       TCP plane is --tcp-opt-in) is disclosed in docs/yang.md's
       implementation section.";
    leaf port {
      type uint16;
      default 8080;
    }
    leaf bind {
      type inet:ip-address;
      default 127.0.0.1;
    }
    leaf socket {
      type string;
      default /run/rouster/restconf.sock;
    }
    leaf token {
      type string {
        pattern '([0-9a-fA-F][0-9a-fA-F])+';
      }
      description
        "Optional static bearer token (hex, case-insensitive, even
         length — the pattern; the bind gate additionally floors it
         at 32 hex chars = 128 bits). Checked on every request when
         configured, constant-time. WRITE-ONLY through the API: it
         is never echoed (a credential echo would hand it to every
         reader of the surface).";
    }
  }

  // ---- the modeled config surface (session + canonical merge) ----

  container ip {
    description "Static routes v4 (the writer's modeled half of the merge).";
    list route {
      key "prefix";
      leaf prefix {
        type inet:ipv4-prefix;
      }
      leaf-list nexthop {
        type union {
          type inet:ipv4-address;
          type enumeration {
            enum blackhole;
          }
        }
      }
    }
  }

  container ipv6 {
    list route {
      key "prefix";
      leaf prefix {
        type inet:ipv6-prefix;
      }
      leaf-list nexthop {
        type union {
          type inet:ipv6-address;
          type enumeration {
            enum blackhole;
          }
        }
      }
    }
  }

  leaf-list route-map {
    description "Verbatim route-map lines (display + canonical pass-through).";
    type string;
  }

  container router {
    list bgp {
      key "local-as";
      leaf local-as {
        type rc:as-number;
      }
      container bgp {
        leaf router-id {
          type inet:ipv4-address;
        }
        leaf network-import-check {
          type boolean;
        }
      }
      list neighbor {
        key "address";
        leaf address {
          type inet:ipv4-address;
        }
        leaf remote-as {
          type rc:as-number;
        }
      }
      container address-family {
        description "`address-family ipv4 unicast` — a two-token container walk.";
        container ipv4 {
          container unicast {
            leaf-list network {
              type inet:ipv4-prefix;
            }
            leaf redistribute {
              type enumeration {
                enum static;
              }
            }
          }
        }
      }
    }
  }
}
